from __future__ import print_function

import FreeCAD
import FreeCADGui
import Points

from pivy import coin

from PySide import QtCore, QtGui
from PySide.QtGui import QTableWidgetItem

import os

def getRelativeFilePath(relativefilename, targetfile):
	return os.path.join(os.path.dirname(relativefilename), targetfile)

class TaskPanel_FemMeshFunctionMeshGroup:
	def __init__(self, obj):

		fn = getRelativeFilePath(__file__, './task_mesh_function.ui')

		self.form = FreeCADGui.PySideUic.loadUi(fn)
		self.obj = obj
		self.actualizeComboBox()

		self.form.comboBoxMeshObject.activated.connect(self.onComboActivated)

	def accept(self):
		FreeCADGui.ActiveDocument.resetEdit()

		self.obj.meshobj = self.form.comboBoxMeshObject.currentText()		

		FreeCAD.ActiveDocument.recompute()
		#FreeCADGui.Control.closeDialog()

		return True

	def reject(self):
		FreeCADGui.ActiveDocument.resetEdit()
		#FreeCADGui.Control.closeDialog()
		return True
		
	def onComboActivated(self, index):
		self.filltable()

	def actualizeComboBox(self):
		self.form.comboBoxMeshObject.clear()
		self.form.comboBoxMeshObject.addItems([o.Label for o in self.obj.Document.Objects if 'FemMesh' in o.PropertiesList])

	def filltable(self):
		meshlabel = self.form.comboBoxMeshObject.currentText()
		meshobj = FreeCAD.ActiveDocument.getObjectsByLabel(meshlabel)[0]

		num_rows = meshobj.FemMesh.GroupCount

		self.form.tableWidget.setRowCount(num_rows)

		available_groups = []
		for i in range(num_rows):
			self.form.tableWidget.setItem(i, 0, QTableWidgetItem(meshobj.FemMesh.getGroupName(i)))
			available_groups.append(meshobj.FemMesh.getGroupName(i))

		self.obj.groups = available_groups
		

class FemMeshFunctionMeshGroup:
	"""
	Create mesh functions for Fenics from FEM_MeshGroup
	"""

	def __init__(self, obj):
		obj.addProperty("App::PropertyString", "meshobj", "", "Selected mesh object").meshobj = ""
		obj.setEditorMode("meshobj", 1)

		obj.addProperty("App::PropertyStringList", "groups", "", "Available Mesh Groups").groups = [""]
		obj.setEditorMode("groups", 1)

		obj.addProperty("App::PropertyStringList", "types", "", "Types of the Groups").types = [""]
		obj.setEditorMode("types", 1)

		obj.addProperty("App::PropertyStringList", "values", "", "Values of the Groups").values = [""]
		obj.setEditorMode("values", 1)


		obj.Proxy = self


class ViewProviderFemMeshFunctionMeshGroup:

	def __init__(self, vobj):
		vobj.Proxy = self

	def attach(self, vobj):
		self.ViewObject = vobj
		self.Object = vobj.Object
		self.standard = coin.SoGroup()
		vobj.addDisplayMode(self.standard, "Standard")

	def getDisplayModes(self, obj):
		return ["Standard"]

	def getDefaulDisplayMode(self):
		return "Standard"

	def updateData(self, obj, prop):
		return

	def onChanged(self, vobj, prop):
		return

	def setEdit(self, vobj, mode=0):
		# show task panel

		taskd = TaskPanel_FemMeshFunctionMeshGroup(self.Object)
		#taskd.obj = vobj.Object
		FreeCADGui.Control.showDialog(taskd)
		return True

	def unsetEdit(self, vobj, mode=0):
		FreeCADGui.Control.closeDialog()
		return

	def doubleClicked(self, vobj):
		doc = FreeCADGui.getDocument(vobj.Object.Document)
		if not doc.getInEdit():
			doc.setEdit(vobj.Object.Name)
		else:
			FreeCAD.Console.PrintError("Active task dialog found! Please close this one first!\n")

	def __getstate__(self):
		return None
	
	def __setstate__(self, state):
		return None


def makeMeshFunction(name="FEMMeshFunction"):
	obj = FreeCAD.ActiveDocument.addObject("Fem::FeaturePython", name)
	FemMeshFunctionMeshGroup(obj)
	if FreeCAD.GuiUp:
		ViewProviderFemMeshFunctionMeshGroup(obj.ViewObject)

	return obj
	
makeMeshFunction()
